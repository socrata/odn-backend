FME workspace node_variable_files.fmw

Parameters:
- DATA_PATH = /Users/alicia.brown/data/odn   # Enter path to data file
- SourceDataset_JSON = $(FME_MF_DIR)data/sources.json   # Source JSON (JavaScript Object Notation) File or URL
- SourceDataset_JSON_3 = Z:\repos\odn-backend\data\sources.json   # Source JSON (JavaScript Object Notation) File or URL
- DestDataset_CSV = /Users/alicia.brown/data/odn   # Destination CSV (Comma Separated Value) Folder

Readers:
- JSON_1: JSON from $(SourceDataset_JSON)
- JSON_2: JSON from $(SourceDataset_JSON_3)

Writers:
- CSV_1: CSV to $(DestDataset_CSV)

Note: Windows: JSONFeature: sources [JSON] - 2
JSONFeature (reader JSON_2) [off]
    attributes: demographics object, education object, jobs object, health object, economy object, crime object, finance object
    -> AttributeExploder
Note: MAC: JSONFeature: sources [JSON] - 1
JSONFeature (reader JSON_1)
    attributes: demographics object, education object, jobs object, health object, economy object, crime object, michigan object
    -> AttributeExploder
AttributeExploder
    ATTR_NAME_LABEL = _attr_name
    ATTR_VALUE_LABEL = _attr_value
    KEEP_ATTRIBUTES = No
    KEEP_GEOMETRY = No
    EXPLODING_TYPE = Features
    -> Tester
Tester
    BOOL_OP = AND
    TEST_DESCRIPTION = ""
    TEST_CLAUSE:
      TEST @Value(_attr_name) NOT_BEGINS_WITH Fme
      TEST @Value(_attr_name) NOT_BEGINS_WITH json
    TEST_MODE = Automatic
    PASSED -> JSONExtractor
JSONExtractor
    EXTRACT_QUERY_TABLE = datasets json["datasets"]
    JSON_DOCUMENT = @Value(_attr_value)
    EVALUATED -> JSONFragmenter
JSONFragmenter
    RECURSIVE = Yes
    JSON_QUERY = json[*]
    EXTRACT_ATTR = Yes
    PREF_STRING = _ids
    JSON_ATTR = datasets
    FRAGMENTS -> AttributeManager
AttributeManager
    ATTR_TABLE:
      RENAME_SET_VALUE _attr_name > topic
      REMOVE _attr_value
      REMOVE datasets
      REMOVE json_type
      RENAME_SET_VALUE json_index > dataset_name
      SET_TO data_file = $(DATA_PATH)/@Value(topic)-@Value(dataset_name).csv
      SET_TO dataset = @Value(topic).@Value(dataset_name)
      SET_TO file = @Value(topic)-@Value(dataset_name).csv
    -> CommandConcatenator
Note: Create the command
Note: NODE Command Runner / Variables Generator
CommandConcatenator: StringConcatenator
    ACTION = Create New Attribute
    PARM_LINE = /usr/local/bin/node data/process/variables.js @Value(dataset) @Value(data_file)
    VAL_ATTR = _result
    -> AttributeKeeper
    -> odn_variable_files (writer CSV_1)
AttributeKeeper
    KEEP_ATTRS = _result
    -> SystemCaller [off]
    -> node_commands (writer CSV_1)
Note: SystemCaller to execute Node commands
SystemCaller
    CMD = @Value(_result)
    -> Logger
Logger
    MAXFEATS = 20
    MAXCOORDS = 20
    MESSAGE = Feature is:
    LOGGED -> inspector
inspector: Inspector
Note: for testing node
node_commands (writer CSV_1)
    attributes: _result auto
Note: For Datasync Runner workflow
odn_variable_files (writer CSV_1)
    attributes: file auto
